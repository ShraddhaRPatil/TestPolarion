# qa

# Specification: QA Power User Training

## MP-3724: Modifying Test Cases (Heading)

### MP-3719: Add custom test case field: precondition (Exercise)
Add custom test case field: precondition
Some test cases have some preconditions which need to be fulfilled before they can be executed. We will add a custom field to our test cases.
Open Administration>Work Items>Custom Fields and select Test Case to define the custom field
- precondition: String
Make precondition visible on top of test case
Our custom field should be visible at the top of our test case layout.
Open Administration>Work Items>Form Configuration and select Test Case layout
Make custom field “precondition” appear in top area of the test case work item

### MP-3720: Add test result: Not Executed (Exercise)
- Currently we have 3 test results: passed, failed and blocked. We want to add another test result “Not Executed” if testing is not performed maybe because a precondition is not fullfilled.
Open Administration>Testing>Test Results and add an additional test result “Not Executed”

## MP-3725: Modifying Test Runs (Heading)

### MP-3721: Change Test Run export template (Exercise)
- If we are going to export our test cases to excel our testers need to know if there are any preconditions. So we want to add our precondition field to our export template.
Open Administration>Testing>Test Export Templates
- Download TestingTemplate.xlsx and save it on your desktop
- Open TestingTemplate.xlsx
- Enable Register card “Polarion” which is hidden by default
- Add precondition field to configuration
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- Save your changed document as “PersonalTemplate.xlsx” an upload your changes.
- (hint) To select a specific export template you need to add a parameter to your export link by customizing your test run page.
e.g. {export-tests:query=type:testcase|template=TestingTemplate.xlsx}

### MP-3722: Add test run status: not executable (Exercise)
- After we have added a new test case result called “Not Executable” we want to add an additional test run status “Not Executable”
Open Administration>Testing>Test Run Statuses and add a new status “Not Executable”

### MP-3723: Add test run custom field: remarks (Exercise)
- We want to track remarks for our test runs so our testers can add some comments about their test run.
Open Administration>Testing>Test Run Custom Fields and add a custom field
- Remarks: text
(hint) If you want to make this custom field visible to your test runs you need to add it to your test run template.
