# wbt session

# Specification: WBT Modules

## MP-3809: About this document (Heading)

### MP-3810: Example Training Session (Heading)

### MP-3811: How To Add a Trainer Script (Heading)

## MP-3046: Polarion FUNDAMENTALS (ALL PRODUCTS) (Heading)

### MP-2151: Polarion Fundamentals - Work Items and Documents (Task)
This training module will introduce Polarion to you and builds the foundation to all other training modules. You will get a general overview on the Polarion product, its features and what benefits Polarion can bring to you and your project team. You will become familiar with the most important artefacts in Polarion: Polarion User Interface, Polarion Work Items and Polarion Documents.
Polarion Documents are essential for people who will create, manage and maintain project documents like requirement specifications, meeting minutes and test specifications.
In this training module you will learn the main principles on how to create, edit and manage Polarion work items and documents.
Agenda
- Introduction
- What is Polarion
- The Polarion User Interface
- Polarion Work Items
- What is a work item?
- Work item fields and their meaning
- 4 different ways to create work items
- Add comments and watch work items
- Polarion Documents
- What is a Polarion Document
- Create and configure Polarion Documents
- Create and manage work items using Polarion Documents
- Document history
- Document comments versus work item comments
- Document Templates
- Requirements:
- none
Recommended Training Modules:
- none

#### MP-4179: Training Configuration & Materials Polarion Fundamentals - Work Items and Documents (Text)
- : WBT Intro Slides used during "Welcome and Introduction"
- TBD WebEx Poll Questions
- Please create PDF and send PDF to students
- Please create PDF and send PDF to students
- no additional documents needed
Project Template for Student & Coach Projects: Software Specificaton Project

#### MP-3839: Trainer Script: Polarion Fundamentals - Work Items and Documents (Text)
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 - The Polarion Portal: 25 minutes
10 Minutes: Slides: Introduction
5 Minutes: Demo Polarion UI
5 Minutes: Exercises MP-3941, MP-2824 - Time for Students to get familiar with Polarion UI
5 Minutes: Wrap-Up questions/polls: You ask questions to see if they understand the concept.
- How do you show navigation pane again ?
- What is displayed by default on your personal home page ?
- What views support display of panes vertically or horizontally?
- When do you need "Text Wrap" option?
Block 2 Understanding Work Items: 25 minutes
10 Minutes: Slides: Work Items
5 Minutes Demo: Demo first two exercise MP-2613 and MP-2616 - include hints which are not on the slides!
5 Minutes Exercise: MP-2613 and MP-2612
5 Minutes: Wrap-Up questions/polls:
- How can new work items created ?
- Can you filter your work item view ?
- What role is needed that a user is selectable as assignee?
- Can you add images to work item description ?
- How can you add a hyperlink to your work item description ?
- What happens if a workflow actions requests a specific field?
Block 3: Work Items - Communication & Collaboration: 20 minutes
5 Minutes Slides: Communication & Collaboration
5 Minutes Demo: Demo next two exercise (MP-2614, MP-2615) - include hints which are not on the slides like how to filter activity streams
5 Minutes Exercise: MP-2614, MP-2615- time for students: trainers mentions relevant exercises in chat - ask student to use chat to give trainer feedback, when they have finished.
5 Minutes: Wrap-Up questions/polls:
- Can you filter activity streams?
Block 4: Documents: 45 minutes
10 Minutes Slides: LiveDocuments
5 Minutes Demo: create and configure a document according MP-2608 (create a blank document, configure the document, create some text, create some headings, create a task item, explain side bar, change properties of the task)
5 Minutes Exercise: MP-2608- time for students: trainers mentions relevant exercises in chat - ask student to use chat to give trainer feedback, when they have finished.
5 Minutes Demo: work with a document (create task work items, create a sub task using tab key, link work items inside same document using link symbol, move and delete work items, add document comments, add a favorite for document) according MP-2627, MP-2609
5 Minutes Exercise: MP-2627, MP-2609- time for students: trainers mentions relevant exercises in chat - ask student to use chat to give trainer feedback, when they have finished.
5 Minutes Demo: document templates accorrding MP-2618 (explain the high level differences. Give an example why these options are available: simple copy for reuse of templates, copy with links to reuse requirements with the option to add new requirements, Dervied with links -> reusing a standard which is not allowed to be changed)
5 Minutes Exercise: MP-2618- time for students: trainers mentions relevant exercises in chat - ask student to use chat to give trainer feedback, when they have finished.
5 Minutes: Wrap-Up questions/polls:
- Why would I use work items for minute meetings and not word or google docs ?
- Why do you think can two people edit in the same document ?
- What type of documents do you think could be interesting to track as live documents apart from meeting minutes
- What will happen if I change a WI in WI editor and not in document editor.
- Can you also have Items as part of a template document ?
- Why would I want items in a template ?
- Would it make sens to have checklists as templates Example (things to check when releasing a product ?)
5 min <Final Q&A>
5 Farewell + Link to Survey

### MP-2364: Polarion Fundamentals - Traceability, Queries and Wiki (Task)
In this training module you will learn more about work item links and how traceability can help you to manage your project and project data in better way. Update work items and use Polarion's suspect mechanism to ensure that your colleagues will get notified on potential inconsistencies regarding their "own" work items. Learn how suspects can help you to answer the four basic questions: WHO, WHAT, WHERE and WHEN.
During the training you will experience various ways to search for data within Polarion. Being familiar with the different search options will speed up your everyday work as information is just a mouse click away.
You will get an short introduction on how to build custom wiki pages to share search results across teams and to guide your colleagues via wiki pages through your process.
Agenda:
- How to keep work items consistent using suspect mechanism
- Understand the difference between traceability and impact
- Different ways to search for project artifacts
- Query builder and filter
- Create own shortcuts and custom saved queries
- Create and edit wiki pages
- How to embed queries and work items in wiki pages
- Example wiki pages: Traceability table, release notes and coverage information
Requirements:
Participants should be familiar with the Polarion UI , the Polarion Work Item concept and Polarion Documents.
Recommended Training Modules:
- Polarion Fundamentals - Work Items and Documents

#### MP-4180: Training Configuration & Materials Polarion Fundamentals - Traceability, Queries and Wiki (Text)
- : WBT Intro Slides used during "Welcome and Introduction"
- TBD WebEx Poll Questions
- Please create PDF and send PDF to students
- Please create PDF and send PDF to students
- no additional documents needed
Project Template for Student & Coach Projects: WBT Fundamentals - Traceability, Queries and Wiki

#### MP-3841: Trainer Script: Polarion Fundamentals - Traceability, Queries and Wiki (Text)
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 - Traceability and Consistency: 35 minutes
10 Minutes: Slides:Traceability and Consistency
5 Minutes: Demo linking work items using tracker, MP-3988
5 Minutes: Exercises MP-3988
5 Minutes: Demo using suspect feature MP-2831 - mention default configuration in administration
5 Minutes: Exercises MP-2831
5 Minutes: Wrap-Up questions/polls: You ask questions to see if they understand the concept.
- What different linking option are you aware of ?
- What is the default behaviour of Polarion concerning suspects ?
- Does suspects help to keep your project consistent ?
- Can you change the default behaviour of Polarion concerning suspects ?
Block 2 Search and Queries: 35 minutes
10 Minutes: Slides: Search and Queries
5 Minutes Demo: Using Polarion queries according MP-2620
5 Minutes Exercise: MP-2620
5 Minutes Demo: Using Polarion search and query option details according MP-2607, MP-2621
5 Minutes Exercise: MP-2607, MP-2621
5 Minutes: Wrap-Up questions/polls:
- Can you filter your work item view ?
- What is the difference between saving a query as query or as shortcut ?
- Is it possible to show the query language of your query ?
Block 3: Wiki: 45 minutes
10 Minutes Slides: Wiki
5 Minutes Demo: create a wiki page (basics and help) according MP-2610
5 Minutes Exercise: MP-2610
5 Minutes Demo: using Polarion wiki macros (basics and help) according MP-2611
5 Minutes Exercise: MP-2611
5 Minutes Demo: using wiki scripts in documents according MP-2606
5 Minutes Exercise: MP-2606
5 Minutes: Wrap-Up questions/polls:
- What can you use wiki pages for ?
- Is it possible to show current project information on your wiki page ?
- How can you access project information using a wiki page ?
- Can you use wiki scripts in your documents ?
5 min <Final Q&A>
5 Farewell + Link to Survey

## MP-3045: Polarion REQUIREMENTS (Heading)

### MP-3035: Polarion REQUIREMENTS - Manage Requirements and Specifications (Task)
This training module explains how work items and documents can be used to elicit, review, approve and manage requirements.
Agenda:
- Track requirements as Work Items
- Create specifications using Polarion Documents
- Integrate existing specifications using Polarion MS Word Import
- Manage document reviews using MS Word Round-trip
- Compare different versions of a specification
Requirements:
Participants should be familiar with the Polarion UI and the Polarion Work Item concept.
Recommended Training Modules:
- Polarion Fundamentals - Work Items and Documents

#### MP-4175: Training Configuration & Materials Polarion Requirements - Manage Requirements and Specifications (Text)
- : WBT Intro Slides used during "Welcome and Introduction"
- Sample WebEx poll file, which can be used in Block 1
- Sample WebEx poll file, which can be used in Block 2
- Sample WebEx poll file, which can be used in Block 3
- Please create PDF and send PDF to students
- Please create PDF and send PDF to students
- Please download and send to students
Project Template for Student & Coach Projects: Software Specificaton Project

#### MP-3837: Trainer Script: Polarion Requirements - Manage Requirements and Specifications (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Author Requirements and Specification: 55 minutes
10 Minutes: Slides: Author Requirements and Specifications
10 Minutes: Demo (creating Requirements, creating a new document, customizing the document)
10 Minutes: Exercises: MP-2559, MP-2648, MP-2653
5 Minutes: Demo (create requirements using documents, document sidebar and work item properties pane)
5 Minutes: Exercises: MP-2649, MP-2654
5 Minutes: Demo (link requirements inside documents, move existing requirements to document, bulk edit of requirements fields)
5 Minutes:Exercises: MP-2650, MP-2651, MP2652
5 Minutes: Wrap-Up questions/polls: You ask questions to see if they understand the concept.
- What is the advantage of two people editing the same document ?
- What types of documents do you think could be interesting to track as live documents ?
- What will happen with document content when I change a WI in WI editor and not in document editor ?
See sample Polling-File "PollManageRequirements.atp" attached to this WI
Block 2 MS Word Import: 30 minutes
5 Minutes: Slides: MS Word Import
10 Minutes Demo: How to import word documents, and how to modify the document afterwards.
10 Minutes Exercises: MP-2658, MP-2886, MP-2887, MP-2888
5 Minutes: Wrap-Up questions/polls: You ask questions to see if they understand the concept.
- Why would I use Polarion documents for requirements specifications and not word or google docs ?
See sample Polling-File "PollWordImport.atp" attached to this WI
Block 3 MS Word Roundtrip: 20 minutes
5 Minutes Slides: MS Word Roundtrip
5 Minutes Demo: Export the Document using Roundtrip, Modify something, add a comment and reimport the document
5 Minutes Exercises: MP-2902, MP2662
5 Minutes: Wrap-Up questions/polls: You ask questions to see if they understand the concept.
- When should somebody use document comments and when Work item comments (document comments when reviewing whole doc, WI comments when discussing on a single WI -> mention that document comments will become more important when collaborating with external people via word
- Is it possible to modify the work item fields included in the roundtrip ?
See sample Polling-File "PollWordRoundtrip.atp" attached to this WI
5 min <Final Q&A>
5 Farewell + Link to Survey

### MP-3036: Polarion REQUIREMENTS - Verification, Validation and Planning (Task)
Traceability is a key element to successfully manage requirements. Practical exercises will teach you how to manage traceability in your projects. You will experience how requirements can be approved and planned to releases
Agenda:
- Link requirements
- Manage multiple Polarion Documents
- Create and link test cases
- Report on coverage and traceability
- Approve requirements
- Assign requirements to releases
Requirements:
Participants should be familiar with the Polarion UI , the Polarion Work Item concept and Polarion Queries
Recommended Training Modules:
- Polarion Fundamentals - Work Items and Documents
- Polarion Fundamentals - Traceability, Queries and Wiki
- Polarion REQUIREMENTS - Manage Requirements and Specifications

#### MP-4176: Training Configuration & Materials Polarion Requirements - Verification, Validation and Planning (Text)
- : WBT Intro Slides used during "Welcome and Introduction"
- Sample WebEx poll file, which can be used in Block 1
- Sample WebEx poll file, which can be used in Block 2
- Please create PDF and send PDF to students
- Please create PDF and send PDF to students
- no additional documents needed
Project Template for Student & Coach Projects: WBT Polarion RM Verification Validation and Planning

#### MP-3838: Trainer Script: Polarion Requirements - Verification, Validation and Planning (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Linking Requirements - Verification and Validation : 70 minutes
10 Minutes: Slides: Linking Requirements - Verification and Validation
10 Minutes: Demo: Manage multiple documents, linking between documents
10 Minutes: Exercises: MP-2665
5 Minutes: Demo: Linking between specification and test cases,
10 Minutes:Exercises: MP-2909
10 Minutes:Demo: Traceability and Coverage using tree and matrix view, wiki reports
10 Minutes:Exercises: MP-2666, MP-2908,
5 Minutes: Wrap-Up questions/polls: You ask questions to see if they understand the concept.
- What are the most common links ?
- What advantages do you get from linking ?
See sample Polling-File "PollLinking.atp" attached to this WI
Block 2 Plan Requirements to Release: 30 minutes
5 Minutes Slides: Planning Requirements to Release
10 Minutes Demo: Approving Requirements and assigning them to a Release
10 Minutes Exercises: MP-2951, MP-2952
5 Minutes: Wrap-Up questions/polls: You ask questions to see if they understand the concept.
- What is the difference between approval by state, or approval by "approvals" section ?
- Call one example for approving by state change and approving using "approvals" !
See sample Polling-File "PollPlaning.atp" attached to this WI
5 min <Final Q&A>
5 Farewell + Link to Survey

### MP-3037: Polarion REQUIREMENTS - Variants and Baselines (Task)
This training module will cover the different ways how requirements can be reused in Polarion. After the training you will know how requirements can be branched to manage different variants of your product. You will be able to decide what reuse approach fits best to your current scenario.
You will experience how baselines can be created to freeze requirements and how Polarion Time-Machine feature enables users to literally go back in time to browse and search the historical state of a project, captured in a baseline.
Agenda
- How to create a branch to manage a variant
- Different behaviour of branched requirements (floating versus frozen requirements)
- How to change and overwrite branched requirements
- How to compare branched requirements to understand changes in a variant
- How to propagate changes to branched requirements
- Create and manage baselines
- Polarion Time-Machine - browse and reference requirements from a specific baseline
Requirements:
Participants should be familiar with the Polarion UI , the Polarion Work Item concept and Polarion Documents
Recommended Training Modules:
- Polarion Fundamentals - Work Items and Documents
- Polarion REQUIREMENTS - Manage Requirements and Specifications
- Polarion REQUIREMENTS - Verifications, Validation and Planning

#### MP-4177: Training Configuration & Materials Polarion Requirements - Variants and Baselines (Text)
- : WBT Intro Slides used during "Welcome and Introduction"
- Sample WebEx poll file, which can be used in Block 1
- Sample WebEx poll file, which can be used in Block 2
- Please create PDF and send PDF to students
- Please create PDF and send PDF to students
- no additional documents needed
Project Template for Student & Coach Projects: WBT Polarion RM Variants and Baselines / Polarion RM Change Management

#### MP-3842: Trainer Script: Polarion Requirements - Variants and Baselines (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Branching Specifications - Variant Management : 50 minutes
10 Minutes: Slides: Branching Specifications - Variant Management
5 Minutes: Demo: Create a branched document
5 Minutes: Exercises: MP-2967
5 Minutes: Demo: Working with branched documents (modify work item in master, freeze/unfreeze/overwrite/remove work items in branched document): use work item properties pane to get more details about selected work item like links
10 Minutes:Exercises: MP-2974, MP-3001
5 Minutes:Demo: Compare master and branched documents, where are my work items used/referenced ?
5 Minutes:Exercises: MP-3080
5 Minutes: Wrap-Up questions/polls: You ask questions to see if they understand the concept.
- What is the main difference between reuse and branch ?
- When do you use branching ?
- Call one example for "reuse document" and one for "branch document" !
- What happens if you overwrite a requirement in a branched document ?
See sample Polling-File "PollBranching.atp" attached to this WI
Block 2 Baselining: 40 minutes
5 Minutes Slides: Baseline and Time Machine
5 Minutes Demo: Create a Baseline
5 Minutes Exercises: MP-2984
5 Minutes Demo: Compare Baselines
5 Minutes Exercises: MP-3179,
5 Minutes Demo: Browse Baselines - Time Machine
5 Minutes Exercises: MP-2985
5 Minutes: Wrap-Up questions/polls: You ask questions to see if they understand the concept.
- When is a baseline marked "italic" in document history ?
- Why is a time machine helpful for audits and assessments ?
- What is are the main differences between the current project and a baseline project ?
- Can you modify a work item or document in a baseline project ?
- What information is displayed for wiki pages in baseline projects ?
See sample Polling-File "PollBaselines.atp" attached to this WI
5 min <Final Q&A>
5 Farewell + Link to Survey

### MP-3295: Polarion REQUIREMENTS - Change Management (Task)
This training module covers how Polarion can help you to analyse the impact of changes as well as how to implement and plan changes to an upcoming release.
Agenda:
- Keep your project artifact consistent using suspects
- Track change requests using Work Items
- Manage changes requests using Polarion Documents
Requirements:
Participants should be familiar with the Polarion UI , the Polarion Work Item concept , Polarion Queries and Polarion Documents.
Recommended Training Modules:
- Polarion Fundamentals - Work Items and Documents
- Polarion Fundamentals - Traceability, Queries and Wiki
- Polarion REQUIREMENTS - Manage Requirements and Specifications
- Polarion REQUIREMENTS - Verification, Validation and Planning
- Polarion REQUIREMENTS - Variants and Baselines

#### MP-4178: Training Configuration & Materials Polarion Requirements - Change Management (Text)
- : WBT Intro Slides used during "Welcome and Introduction"
- Sample WebEx poll file, which can be used in Block 1
- Please create PDF and send PDF to students
- Please create PDF and send PDF to students
- no additional documents needed
Project Template for Student & Coach Projects: WBT Polarion RM Variants and Baselines / Polarion RM Change Management

#### MP-3843: Trainer Script: Polarion Requirements - Change Management (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Handling Changes: 65 minutes
10 Minutes: Slides: Handling Changes
5 Minutes: Demo: Document Auto Suspect
5 Minutes: Exercises: MP-3583
5 Minutes: Demo: Create and diiscuss work item "change request". Create and link tasks for change request
5 Minutes:Exercises: MP-2973
5 Minutes:Demo: Impact Analyse
5 Minutes:Exercises: MP-2986
5 Minutes: Demo: Impact and Change Document concept
15 Minutes: Exercises: MP-3579
5 Minutes: Wrap-Up questions/polls: You ask questions to see if they understand the concept.
- What do you think about using a document for your change documentation ?
See sample Polling-File "PollChange.atp" attached to this WI
5 min <Final Q&A>
5 Farewell + Link to Survey

## MP-3047: Polarion QA (Heading)

### MP-2158: Polarion QA - Author Test Cases and Test Specifications (Task)
In this module you will learn how Polarion can help you to manage your QA activities. You will experience how test cases can be created, edited and reviewed using Polarion documents.
Agenda
- Create, manage and organize test cases in LiveDocs
- Import test cases from MS Excel
- Collaborate using MS Excel Round trip

#### MP-4788: Training Configuration & Materials Polarion QA - Author Test Cases and Test Specifications (Text)
Documents for Trainer:
- : WBT Intro Slides used during "Welcome and Introduction"
- Documents for Students:
- Please create PDF and send PDF to students
- Please create PDF and send PDF to students
Documents needed for Exercises:
- Save the example Test specifcation document provided on
Project Configuration:
Project Template for Student & Coach Projects: Software Specificaton Project

#### MP-4789: Trainer Script: Polarion QA - Author Test Cases and Test Specifications (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Handling Changes: 95 minutes
10 Minutes: Slides: Work Items
5 Minutes: Demo: Track test cases as work items
5 Minutes: Exercises: MP-2746
10 Minutes: Slides: Live Documents
5 Minutes: Demo: Create test specifications using Polarion Live Documents, Add test cases to specification
15 Minutes: Exercises: MP-2747, MP-2750
10 Minutes: Slides: MS Excel Integration
10 Minutes: Demo: Importing an Excel Spreadsheet, Using Excel Round-trip
20 Minutes: Exercises: MP-4848, MP-3003
5 Minutes: Wrap-Up questions/polls: You ask questions to see if they understand the concept.
- TBD
See sample Polling-File "TBD" attached to this WI
5 min <Final Q&A>
5 Farewell + Link to Survey

### MP-3729: Polarion QA - Coverage and Traceability (Task)
In this module you will learn how Polarion can help you to manage your QA activities. You will experience how test cases can be linked to requirements and how you can verify which requirements have already been covered by test cases and which not.
Agenda
- Create and link test cases to requirements
- Manage Potential Change Impacts

#### MP-4812: Training Configuration & Materials Polarion QA - Coverage and Traceability (Text)
Documents for Trainer:
- : WBT Intro Slides used during "Welcome and Introduction"
- Documents for Students:
- Please create PDF and send PDF to students
- Please create PDF and send PDF to students
Documents needed for Exercises:
- no additional documents needed
Project Configuration:
Project Template for Student & Coach Projects: Software Specificaton Project

#### MP-4813: Trainer Script: Polarion QA - Coverage and Traceability (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Handling Changes: 35 minutes
10 Minutes: Slides: Traceability And Consistency
5 Minutes: Demo: Link Testcases with requirements, Create a testcase from a requirement
5 Minutes: Exercises: MP-2751, MP-2755
5 Minutes:Demo: Update a test case on a changed requirement
5 Minutes:Exercises: MP-2761
5 Minutes: Wrap-Up questions/polls: You ask questions to see if they understand the concept.
- TBD
See sample Polling-File "TBD" attached to this WI
5 min <Final Q&A>
5 Farewell + Link to Survey

### MP-2160: Polarion QA - Test Case Planning, Execution and Defect Tracking (Task)
In this module you will categorize test cases into different groups and you will learn how test cases can be organized into bigger test scenarios (test runs) based on custom criteria. You will focus on test case planning and test case execution. You will learn how test plans containing different test activities can be created, how activities can be assigned to testers and how testers can execute test cases and report defects in case of failure. You will be familiar with the different options to execute test cases in Polarion and you will know how to review the current status of you QA activities.
Agenda
- Create a test plan which aggregates multiple test runs
- Managing test scenarios
- How to assign a test scenario to a tester
- Execute test cases in Polarion
- How to report a defect
- Execute test cases offline and upload results

#### MP-4821: Training Configuration & Materials Polarion QA - Test Case Planning, Execution and Defect Tracking (Text)
Documents for Trainer:
- : WBT Intro Slides used during "Welcome and Introduction"
- Documents for Students:
- Please create PDF and send PDF to students
- Please create PDF and send PDF to students
Documents needed for Exercises:
- Selenium file stored at
Project Configuration:
Project Template for Student & Coach Projects: Software Specificaton Project

#### MP-4822: Trainer Script: Polarion QA - Test Case Planning, Execution and Defect Tracking (Text)
Time schedule:
Welcome and Introduction: 15 minutes
- Welcome
Introduce yourself
- Webex How-To
- exercise audio/chat: round of introductions
trainer uses chat to give students topics and ideas for their introduction
- exercise: share your screen
every student shares his screen - trainer checks whether students have successfully logged in to Polarion and use the correct project
- exercise: add link to survey to chat panel
- Agenda of today's WBT
Block 1 Handling Changes: 95 minutes
5 Minutes: Slides: Test Planning
5 Minutes: Demo: Using document templates
5 Minutes: Exercises: MP-2763
5 Minutes: Demo: Reuse test cases and test scenarios
5 Minutes:Exercises: MP-2764
5 Minutes:Demo: Create an overall test plan
5 Minutes:Exercises: MP-2765
5 Minutes: Slides: Test Execution
5 Minutes: Demo: Executing test cases online
5 Minutes: Exercises: MP-2766
5 Minutes: Demo: Executing test cases using excel
10 Minutes: Exercises: MP-2767
5 Minutes: Demo: Tracking defects for failed test cases
5 Minutes: Exercises: MP-2768
5 Minutes: Slides: Developing With Polarion
5 Minutes: Demo: How to integrate with test automation tools
5 Minutes: Exercises: MP-2770
5 Minutes: Wrap-Up questions/polls: You ask questions to see if they understand the concept.
- TBD
See sample Polling-File "TBD" attached to this WI
5 min <Final Q&A>
5 Farewell + Link to Survey

## MP-3048: Polarion Administration / Power User Modules (Heading)

### MP-2161: Work items, Fields and Workflow (Task)
This training module will make you familiar with the most essential configuration options of Polarion and represents the starting point for a successful Polarion configuration. You will learn how to define custom work items, custom fields, custom field values and you will understand the different field types which are available. You will understand how to setup a workflow representing your way of working. Additional to the basic workflow model and your workflow will also support required fields and constraints which check what role is entitled to perform the next status change.
Agenda
- Understand global and project specific configuration
- Define custom work item types
- Define custom workflow (status, actions, role specific constraints, required fields)
- Define custom fields (date fields, enumeration fields, string fields ...)
- Define custom field values (custom enumerations)

### MP-2363: Custom Links, Linking Meta-Model, Calculated Fields (Task)
In this training module you will learn how to define the meta-model of your work items, what link roles are available, what work items are allowed to be linked with other work items, in which direction can work items be linked together and what menus will be available to create linked work items. This will ensure for example that test cases can only be linked to requirements with a verification link role. You will learn how link roles can be helpful to calculate field values from child work items.
Agenda
- Define custom link roles
- Define a linking meta-model
- Define custom menus and menu actions to link and create work items
- Define calculated fields

### MP-2162: Views, Layout And Read-Only Configuration (Task)
In this training module you will learn to customize Polarion to support different views for different people on your project data. Role based views will allow to define what topics a user can see, what fields can be editied and when, freeze specific fields based on work item status and to layout work item fields according to a defined workflow.
Agenda
- Custom views (assign views to roles, define custom views, define available topics)
- Custom layout for work item fields
- Display different fields based on status and role
- Define read-only fields based on status and view
- Custom menus for different work items

### MP-2163: Notification And Auto Assignment (Task)
This training module will make you familiar with the different notification settings which can be defined in Polarion. You will learn to customize when, under which conditions and to whom Polarion will send notification emails. Define look and layout of emails and learn how work items can automatically be assigned to team members based on rules you have defined.
Agenda
- custom notification rules
- custom email layouts based on events
- work item specific email layouts
- auto assignment of work items

### MP-2166: Reports, Charts and Metrics (Task)
This training will make you familiar with the different options to visualize and aggregate project data in different ways. You will understand how wiki pages can be used to display custom reports such as lists, counts, charts and bar graphs.
Agenda
- Use Polarion wiki to build custom report pages (embed work items in wiki pages, embed queries in wiki pages, predefined wiki macros)
- How to display trend charts in wiki pages
- How to display bar graphs in wiki pages
- Define custom metrics and display them in wiki pages

### MP-2164: Projects, User Management And Access Rights (Task)
In this training module you will learn how create, manage and secure projects using Polarion. You will understand the difference between global roles and project roles and you will experience how users can have different roles and access rights in different projects.
Agenda:
- Creating Projects
- Create and edit Users
- Assign users to roles and projects
- Global roles and project roles
- Role based permissions
- Subversion access rights
