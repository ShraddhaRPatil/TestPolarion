# handoutsPlanning

# Specification: Handout Easy Planning

## TM-5176: Create a website
Create a website
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
## TM-5177: Create a release
Create a release
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
## TM-5180: Prioritize
Prioritize
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
## TM-5178: Create an iteration
Create an iteration
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
## TM-5179: Using a task board
Using a task board
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
# Specification: Handout Easy Planning Administration

## TM-5181: Typical Release Structure
Typical Release Structure
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
## TM-5182: Multiple Team Structure
Multiple Team Structure
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
## TM-5184: Add Approval State to plans
Add Approval State to plans
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
## TM-5185: Automatic calculation of work records
Automatic calculation of work records
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
## TM-5186: Add planning for your testing team
Add planning for your testing team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

# Specification: Handout Document Administration

## TM-5187: Add document meta data
Add document meta data
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
## TM-5189: Create Document Workflow
Create Document Workflow
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