# planningTraining

# Specification: Planning Training

## TM-5154: User Training (Heading)

### TM-5157: Create Items for planning (Exercise)
To start planning in Polarion we first need to have items, releases and iterations.
- Create 2 example requirements
- Add initial estimate of 4 days
- Add yourself as assignee
- Create a defect and an implementation task for both requirements
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- Create 2 new iterations "Iteration 2" and "Iteration 3" as sub plans for release "Version 1.0"

### TM-5158: Add Requirements to release and prioritize (Exercise)
- Open release "Version 1.0" and add your newly created requirements to existing plan
(Don´t forget to save your plan after adding your items)
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- By default your requirements have a priority of 50. Increase priority of your new requirments so they are on top of your release backlog.
- Verify Statistics, Child Plans and Planned items are displayed correctly (your requirements should be on top of your backlog)
- Set release to "In Progress" and refresh your plan to start calculation of your plan
| Hint: You can use drag and drop or arrow / plus keys to increase / decrease or add / remove your items |
| --- |

#### TM-5160: Add items to an iteration (Exercise)
Before we start working on our tasks and defects we need to setup a Start Date, Due Date and we need to select the items we are planning for this iteration.
- Select "Iteration 2" in Plans section
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- Set as "Start Date" todays date and as "Due Date" 7 days later. So our Iteration will take 1 week.
- We also set a capacity of 40 hours which means 1 person is working on this iteration (5 working days * 8 hours)
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- Add our 2 requirements to this iteration and check calculation on the right planning sidebar.
(Remember, we have added an initial estimate of 4 days for each requirment and our current capacity is set to 1 person working 5 days)
| Hint: In properties configuration you can define a "Default Estimate" (input in hours) for work items which currently have no estimation. |
| --- |
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- Set Status of "Iteration 2" to "In Progress" and refresh plan to start calculation
| Hint: By default you can only add requirements to an iteration which have been planned in a parent (release) plan |
| --- |

#### TM-5161: Work on your tasks and defects (Exercise)
After setting up a release and an iteration we can start to implement, test and fix our work product.
- Open "Iteration 2" and scroll down to Plan Board (you can also use "Plan Board hyperlink on top)
- You should see both requirments, their sub tasks and defects and also the state of tasks and defects. At the right side of your requirement you should see yourself as assignee and you remaining estimate.
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- Open tasks/defects and change their status. After refreshing your Plan you will see all status changes in your plan board.
- Add 4d to your time spent attribute of your first requirement and 1d to your second requirement.
Your Plan board might look like this:
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- Lets say we are finished with our iteration. We´ve got still 3 days of work open in our second requirment but we will transfer this open requirment to our next iteration. Set the status of your plan to "Done"
| Hint: A historical state of your plan will be saved. Even if you move an item into its next iteration you can go back and have a look how your plan looked like when you were finished. |
| --- |

#### TM-5162: Move open tasks into next iteration (Exercise)
Our first iteration is finished and work which is still open needs to be moved into our next iteration.
- Open "Iteration 3"
- Set "Start Date" (today), "Due Date" (in 2 weeks) and capacity (40)
- Add your second requirement which is not yet finished to "Iteration 3"
- Save Plan
- Check your moved requirement. Via your "Planned In" attribute you can always see in which iteration or release your requirement was planned.
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As you can see all data has been moved correctly. 1 day time spent is already booked on our requirement and your task and defect are on their correct spot.
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| Hint: If you make changes on plan board in "Iteration 3" these changes will also been done on "Iteration 2". Via your saved historical link you can always go back in time to view you plan how it looked like when it was finished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 |
| --- |

## TM-5155: Admin Training (Heading)

### TM-5159: Create a multi team and multiple milestone structure (Exercise)
As project manager you might want to setup multiple milestones during a year and work with multiple teams. A deeper hierarchie than "Release -> Iteration" is needed.
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- Open Plan Properties of "Version 1.0" and rename your plan to current year while being in edit mode
- Create new sub release "MS 1" (Parent of MS 1 should be previously changed year release)
- Create below "MS1" 2 sub releases "Team 1" and "Team 2" as displayed on image above
- We still have to move our existing iteration(s) into our team space. Select "Iteration 1", open Properties and change "Parent" atribute to "Team_1"
- Save your changes and refresh your browser window to see your updated structure

### TM-5163: Add Approval Plan State (Exercise)
You might want to add an approval status to your plan when your iteration has been finished.
- Open Administration>Plans>Plan Statuses
- Add new status "approved" at the bottom of statuses list
- Our new approved field should be our final state also having a time stamp when it reached its state. Currently the final state is state "done" marked via "Terminal" checkbox set. Unmark terminal checkbox on state "done" and set Terminal checkbox on approved state.
- Verify in frontend your functionality is working as expected
- Set a Plan to state "Done" (no time stamp should be visible)
- Set a Plan to state "Approved" (time stamp should be visible and historical state of your plan is saved)
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| Hint: Terminal statuses will add a time stamp and make plans invisible in navigation sidebar |
| --- |

### TM-5164: Calculate time spent of your implementing tasks and defects to your requirements (Exercise)
In default configuration time which is booked on tasks or defects isn´t calculated automatically to their requirements they are implementing.
Open Administration>Work Items>Calculated Fields and setup calculated field timeSpent for work item type "Requirement"
- Set "Calculated Field ID" to "timeSpent"
- Set calculation to sum and add timeSpent as "Source Field ID" calculated from "Chield field"
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- Verify calculation is working in frontend by inserting an initial estimate to a requirement and book some time on sub task which is linked to your requirement via "implements" link role

### TM-5170: Create Test Plan Template (Exercise)
Usually it makes sense to setup tasks for test planning and execution but lets assume we want to see test cases in our Plans.
- Go into Administartion > Plans > Plan Templates
- Create a new template based on "Iteration" called "Test"
- Open Plan properties
- Remove requirement and add test cases as allowed types
- Change color of test plan to "yellow"
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
### TM-5165: Make Test Cases visible for Live Plan (Exercise)
By default test cases are not visible in Live Plan but by adding test cases to plans we will be able to see test cases.
- Open Administration > Work Items > Live Plan
- As we can see by default everything which has been added to a plan will also be visible in Live Plan
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- Go to frontend and create a new "Test" Plan (Child of Team 1) "Test Iteration 1"
- Set a start and du date
- Add test case to "Test Iteration 1"
- Verify test case is now visible in live plan
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- (optional) Currently there isn´t any "Planned In" attribute visible in test cases. To add this attribute Go into Administartion > Work Items > Form Configuration > Form Layout of Test Case
- Add <field id="plannedIn"/> to your form configuration
- Verify Planned In field is visible in frontend
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| Hint: In older Polarion versions Live Plan query was set to "time points" |
| --- |

## TM-5171: Document Administration (Heading)

### TM-5174: Create a custom field for documents (Exercise)
If you want to add some meta data to your specifications you can add custom fields for specifications.
- Open Administration > Documents & Wiki > Document Custom Fields
- Add a custom field:
- Id = document_owner
- Name = Document Owner
- Type: enum (User)
- (optional) add a role to limit user selection
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| Hint: Document custom fields are not type specific like in work items. Document custom fields will be available in all specification types. |
| --- |

### TM-5173: Create document type and document workflow for a test specification (Exercise)
By default you track your process via Work Items but sometimes you also want to track your process by defining a workflow for your document. To select a document workflow during document creation or import we need to define a document type and its corresponding workflow.
- Open Administration > Documents & Wiki > Document Types
- Add a configuration for test specifications called "Test Specification"
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- Open Administration > Documents & Wiki > Document Workflow and create a new workflow for "Test Specification"
- We will create a smilar workflow as for single test cases.
- As statuses we use "Draft" (initial), "Active" and "Inactive"
- As actions we use "activate" and "deactivate"
- Define transitions:
- Draft -> Active via activate
- Draft -> Inactive via deactivate
- Active -> Inactive via deactivate
- Inactive -> Active via activate
- For action "activate" we want our users to set our custom field "document_owner" as required field.
If we want to "deactivate" a specification our custom field "document_owner" should be cleared.
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- Verify your document workflow and required / cleared fields are working as configured by creating / modifying a test specification.
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| Hint: You can also define advanced workflow rules to use functions and conditions. e.g. to change status of all contained work items of a specification. |
| --- |
